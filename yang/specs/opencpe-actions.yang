module opencpe-actions {

    namespace "urn:opencpe:actions";
    prefix "ocpe-action";

    include opencpe-actions-meta-extensions;

    ocpe-action:annotate "/sys:system/sys:ntp/sys:server/sys:udp/sys:address" {
        ocpe-action:action "dm_ntp";
    }

    ocpe-action:annotate "/sys:system/sys:ntp/sys:server/sys:udp/sys:port" {
        ocpe-action:action "dm_ntp";
    }

    ocpe-action:annotate "/sys:system/sys:dns-resolver/sys:server/sys:udp-and-tcp/sys:address" {
        ocpe-action:action "dm_dns";
    }

    ocpe-action:annotate "/sys:system/sys:dns-resolver/sys:server/sys:udp-and-tcp/sys:port" {
        ocpe-action:action "dm_dns";
    }

    ocpe-action:annotate "/sys:system/sys:dns-resolver/sys:search" {
        ocpe-action:action "dm_dns";
    }

    ocpe-action:annotate "/if:interfaces/if:interface/ip:ipv4/ip:address/ip:ip" {
        ocpe-action:action "dm_if_ip";
    }

    ocpe-action:annotate "/if:interfaces/if:interface/ip:ipv4/ip:address/ip:prefix-length" {
        ocpe-action:action "dm_if_ip";
    }

    ocpe-action:annotate "/if:interfaces/if:interface/ip:ipv6/ip:address/ip:ip" {
        ocpe-action:action "dm_if_ip";
    }

    ocpe-action:annotate "/if:interfaces/if:interface/ip:ipv6/ip:address/ip:prefix-length" {
        ocpe-action:action "dm_if_ip";
    }

    ocpe-action:annotate "/if:interfaces/if:interface/ip:ipv4/ip:neighbor/ip:ip" {
        ocpe-action:action "dm_if_neigh";
    }

    ocpe-action:annotate "/if:interfaces/if:interface/ip:ipv4/ip:neighbor/ip:link-layer-address" {
        ocpe-action:action "dm_if_neigh";
    }

    ocpe-action:annotate "/if:interfaces/if:interface/ip:ipv6/ip:neighbor/ip:ip" {
        ocpe-action:action "dm_if_neigh";
    }

    ocpe-action:annotate "/if:interfaces/if:interface/ip:ipv6/ip:neighbor/ip:link-layer-address" {
        ocpe-action:action "dm_if_neigh";
    }
}
