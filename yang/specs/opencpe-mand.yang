module opencpe-mand {

    namespace "urn:opencpe:mand";

    prefix "ocpemand";

    import ietf-interfaces {
        prefix "if";
        revision-date 2013-07-04;
    }
    import ietf-ip {
        prefix ip;
    }
    import ietf-inet-types {
        prefix inet;
    }

    organization
        "Travelping GmbH";

    contact
        "Röntgenstraße 13
        39108 Magdeburg
        Editor: Sascha Kattelmann <sk@travelping.com>";

    description
        "This module contains specific augmentations for mand.";

    augment "/if:interfaces-state/if:interface" {
        leaf last-read{
            type string;
        }
    }

    /*
     * FIXME: We could map all routes into the data model instead
     * of only the default gateways.
     */
    augment "/if:interfaces-state/if:interface/ip:ipv4" {
        leaf-list gateway-ip {
            type inet:ipv4-address-no-zone;
            description
                "A list of gateway addresses.";
        }
    }

    augment "/if:interfaces-state/if:interface/ip:ipv6" {
        leaf-list gateway-ip {
            type inet:ipv6-address-no-zone;
            description
                "A list of gateway addresses.";
        }
    }
}
