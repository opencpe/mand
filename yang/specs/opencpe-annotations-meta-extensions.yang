submodule opencpe-annotations-meta-extensions {

    belongs-to opencpe-annotations {
        prefix ocpe-annotation;
    }

    extension substatement {
        argument name;
        description
            "Specifies which statements can occur as substatement to the
            given statement.";
    }

    extension arg-type {
        ocpe-annotation:substatement "type";
            description
                "Specifies the type of the argument.";
    }

    extension use-in {
        argument name;
        description
            "Specifies in which statements a 
            particular extension statement can be used.";
    }

    extension annotate {
        argument target {
            ocpe-annotation:arg-type {
                type string;
            } 
        }
        ocpe-annotation:use-in "module";
        ocpe-annotation:use-in "submodule";
        ocpe-annotation:substatement "tailf:annotate";
        description
            "The substatements on an annotation are treated as if they are written inline.";
    }

    extension action {
        argument id {
            ocpe-annotation:arg-type {
                type string;
            }    
        }    
        ocpe-annotation:use-in "leaf";
        ocpe-annotation:use-in "leaf-list";
        ocpe-annotation:use-in "list";
        ocpe-annotation:use-in "container";
    }
    extension flags {
        argument id {
            ocpe-annotation:arg-type {
                type string;
            }    
        }    
        ocpe-annotation:use-in "leaf";
        ocpe-annotation:use-in "leaf-list";
        ocpe-annotation:use-in "list";
        ocpe-annotation:use-in "container";
    }
    extension getter {
        argument id {
            ocpe-annotation:arg-type {
                type string;
            }    
        }    
        ocpe-annotation:use-in "leaf";
        ocpe-annotation:use-in "leaf-list";
        ocpe-annotation:use-in "list";
        ocpe-annotation:use-in "container";
    }
    extension setter {
        argument id {
            ocpe-annotation:arg-type {
                type string;
            }    
        }    
        ocpe-annotation:use-in "leaf";
        ocpe-annotation:use-in "leaf-list";
        ocpe-annotation:use-in "list";
        ocpe-annotation:use-in "container";
    }
    extension type {
        argument id {
            ocpe-annotation:arg-type {
                type string;
            }    
        }    
        ocpe-annotation:use-in "leaf";
        ocpe-annotation:use-in "leaf-list";
        ocpe-annotation:use-in "list";
        ocpe-annotation:use-in "container";
    }

}
