module opencpe-annotations {

    namespace "urn:opencpe:annotations";
    prefix "ocpe-annotation";

    include opencpe-annotations-meta-extensions;

    ocpe-annotation:annotate "/sys:system/sys:clock/sys:timezone-utc-offset" {
        ocpe-annotation:flags "f_system";
        ocpe-annotation:getter true;
    }

    ocpe-annotation:annotate "/sys:system-state/sys:clock/sys:current-datetime" {
        ocpe-annotation:flags "f_system";
        ocpe-annotation:getter true;
        ocpe-annotation:setter true;
    }

    ocpe-annotation:annotate "/sys:system/sys:ntp/sys:enabled" {
        ocpe-annotation:action "dm_ntp";
    }

    ocpe-annotation:annotate "/sys:system/sys:ntp/sys:server/sys:udp/sys:address" {
        ocpe-annotation:action "dm_ntp";
    }

    ocpe-annotation:annotate "/sys:system/sys:ntp/sys:server/sys:udp/sys:port" {
        ocpe-annotation:action "dm_ntp";
    }

    ocpe-annotation:annotate "/sys:system/sys:dns-resolver/sys:server/sys:udp-and-tcp/sys:address" {
        ocpe-annotation:action "dm_dns";
    }

    ocpe-annotation:annotate "/sys:system/sys:dns-resolver/sys:server/sys:udp-and-tcp/sys:port" {
        ocpe-annotation:action "dm_dns";
    }

    ocpe-annotation:annotate "/sys:system/sys:dns-resolver/sys:search" {
        ocpe-annotation:action "dm_dns";
    }

    ocpe-annotation:annotate "/sys:system/sys:authentication/sys:user/sys:name" {
        ocpe-annotation:action "dm_authentication";
    }

    ocpe-annotation:annotate "/sys:system/sys:authentication/sys:user/sys:password" {
        ocpe-annotation:action "dm_authentication";
    }

    ocpe-annotation:annotate "/if:interfaces/if:interface/ip:ipv4/ip:address/ip:ip" {
        ocpe-annotation:action "dm_if_ip";
    }

    ocpe-annotation:annotate "/if:interfaces/if:interface/ip:ipv4/ip:address/ip:netmask" {
        ocpe-annotation:flags "f_system";
        ocpe-annotation:getter true;
        ocpe-annotation:setter true;
        ocpe-annotation:action "dm_if_ip";
    }

    ocpe-annotation:annotate "/if:interfaces/if:interface/ip:ipv4/ip:address/ip:prefix-length" {
        ocpe-annotation:setter true;
        ocpe-annotation:action "dm_if_ip";
    }

    ocpe-annotation:annotate "/if:interfaces/if:interface/ip:ipv6/ip:address/ip:ip" {
        ocpe-annotation:action "dm_if_ip";
    }

    ocpe-annotation:annotate "/if:interfaces/if:interface/ip:ipv6/ip:address/ip:prefix-length" {
        ocpe-annotation:action "dm_if_ip";
    }

    ocpe-annotation:annotate "/if:interfaces/if:interface/ip:ipv4/ip:neighbor/ip:ip" {
        ocpe-annotation:action "dm_if_neigh";
    }

    ocpe-annotation:annotate "/if:interfaces/if:interface/ip:ipv4/ip:neighbor/ip:link-layer-address" {
        ocpe-annotation:action "dm_if_neigh";
    }

    ocpe-annotation:annotate "/if:interfaces/if:interface/ip:ipv6/ip:neighbor/ip:ip" {
        ocpe-annotation:action "dm_if_neigh";
    }

    ocpe-annotation:annotate "/if:interfaces/if:interface/ip:ipv6/ip:neighbor/ip:link-layer-address" {
        ocpe-annotation:action "dm_if_neigh";
    }

    ocpe-annotation:annotate "/if:interfaces-state/if:interface/if:admin-status" {
        ocpe-annotation:getter true;
    }

    ocpe-annotation:annotate "/if:interfaces-state/if:interface/ocpemand:last-read" {
        ocpe-annotation:flags "f_read;f_write;f_internal;f_datetime";
        ocpe-annotation:type "t_ticks";
    }

    ocpe-annotation:annotate "/if:interfaces-state/if:interface/ip:ipv4/ip:address/ip:netmask" {
        ocpe-annotation:flags "f_system";
        ocpe-annotation:getter true;
    }

}
