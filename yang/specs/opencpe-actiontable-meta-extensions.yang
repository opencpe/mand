submodule opencpe-actiontable-meta-extensions {

    belongs-to opencpe-actiontable {
        prefix ocpe-actiontable;
    }

    extension substatement {
        argument name;
        description
            "Specifies which statements can occur as substatement to the
            given statement.";
    }

    extension arg-type {
        ocpe-actiontable:substatement "type";
            description
                "Specifies the type of the argument.";
    }

    extension use-in {
        argument name;
        description
            "Specifies in which statements a 
            particular extension statement can be used.";
    }

    //the entries of one action field
    extension include {
        argument arg {
            ocpe-actiontable:arg-type {
                type string;
            } 
        }
    }
    extension comment {
        argument arg {
            ocpe-actiontable:arg-type {
                type string;
            } 
        }
    }
    extension sel {
        argument arg {
            ocpe-actiontable:arg-type {
                type string;
            } 
        }
    }
    extension pre {
        argument arg {
            ocpe-actiontable:arg-type {
                type string;
            } 
        }
    }
    extension action {
        argument arg {
            ocpe-actiontable:arg-type {
                type string;
            } 
        }
    }
    extension post {
        argument arg {
            ocpe-actiontable:arg-type {
                type string;
            } 
        }
    }
    extension chain {
        argument arg {
            ocpe-actiontable:arg-type {
                type string;
            } 
        }
    }

    extension action-field {
        argument action-name {
            ocpe-actiontable:arg-type {
                type string;
            } 
        }
        ocpe-actiontable:use-in "module";
        ocpe-actiontable:use-in "submodule";
    }

}
