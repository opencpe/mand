submodule opencpe-actions-meta-extensions {

    belongs-to opencpe-actions {
        prefix ocpe-action;
    }

    extension substatement {
        argument name;
        description
            "Specifies which statements can occur as substatement to the
            given statement.";
    }

    extension arg-type {
        ocpe-action:substatement "type";
            description
                "Specifies the type of the argument.";
    }

    extension use-in {
        argument name;
        description
            "Specifies in which statements a 
            particular extension statement can be used.";
    }

    extension annotate {
        argument target {
            ocpe-action:arg-type {
                type string;
            } 
        }
        ocpe-action:use-in "module";
        ocpe-action:use-in "submodule";
        ocpe-action:substatement "tailf:annotate";
        description
            "The substatements on an annotation are treated as if they are written inline.";
    }

    extension action {
        argument id {
            ocpe-action:arg-type {
                type string;
            }    
        }    
        ocpe-action:use-in "leaf";
        ocpe-action:use-in "leaf-list";
        ocpe-action:use-in "list";
        ocpe-action:use-in "container";
    }

}
